(Defun C:Zvaigzde()
  (setq centras (getpoint "\nNurodykite zvaigzdes centra: "))
   (setq radius (getdist "\nNurodykite zvaigzdes spinduli: "))
  (command "osnap" "off")
   (command "lweight" "0.5")
   (command "polygon" "3" centras "I" radius)
   (setq rotate (entlast))
   (command "rotate" rotate "" centras "180")
   (command "polygon" "3" centras "I" radius)
)
