(Defun C:Kamuolys()
  (setq bazinis (getpoint "\nNurodykite kamuolio bazini taska: "))
   (setq taskas1 (list(- (car bazinis) 30)(cadr bazinis)))
   (setq taskas2 (list(+ (car bazinis) 30)(cadr bazinis)))
   (setq taskas3 (list(car bazinis)(- (cadr bazinis) 30)))
   (setq taskas4 (list(car bazinis)(+ (cadr bazinis) 30)))
   (setq lankas11 (list(- (car bazinis) 21)(+ (cadr bazinis) 21)))
   (setq lankas12 (list(- (car bazinis) 8)(+ (cadr bazinis) 0)))
   (setq lankas13 (list(- (car bazinis) 21)(- (cadr bazinis) 21)))
   (setq lankas21 (list(+ (car bazinis) 21)(+ (cadr bazinis) 21)))
   (setq lankas22 (list(+ (car bazinis) 8)(+ (cadr bazinis) 0)))
   (setq lankas23 (list(+ (car bazinis) 21)(- (cadr bazinis) 21)))
  (command "osnap" "off")
   (command "circle" bazinis "30")
   (setq circle (entlast))
   (command "hatch" "" bazinis circle "")
   (command "-hatchedit" bazinis "CO" "T" "205,105,40" "")
   (command "line" taskas1 taskas2 "")
   (command "line" taskas3 taskas4 "")
   (command "arc" lankas11 lankas12 lankas13)
   (command "arc" lankas21 lankas22 lankas23)
)
