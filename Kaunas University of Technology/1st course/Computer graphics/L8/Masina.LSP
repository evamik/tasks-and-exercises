(Defun C:Masina()
  (setq bazinis (getpoint "\nNurodykite masinos bazini taska: "))
   (setq ratas1 (list(- (car bazinis) 20)(cadr bazinis)))
   (setq ratas1arc1 (list(- (car ratas1) 7)(cadr bazinis)))
   (setq ratas1arc2 (list(+ (car ratas1) 7)(cadr bazinis)))
   (setq ratas2 (list(+ (car bazinis) 20)(cadr bazinis)))
   (setq ratas2arc1 (list(- (car ratas2) 7)(cadr bazinis)))
   (setq ratas2arc2 (list(+ (car ratas2) 7)(cadr bazinis)))
   (setq riemasg1 (list(- (car ratas1arc1) 3)(cadr bazinis)))
   (setq riemasg2 (list(car riemasg1)(+ (cadr riemasg1) 12)))
   (setq riemasg3 (list(+ (car riemasg2) 10)(cadr riemasg2)))
   (setq riemasp1 (list(+ (car ratas2arc2) 6)(cadr bazinis)))
   (setq riemasp2 (list(car riemasp1)(+ (cadr riemasp1) 8)))
   (setq riemasp3 (list(- (car riemasp2) 20)(cadr riemasg2)))
   (setq stogas (list(car bazinis)(+ (cadr bazinis) 25)))
  (command "osnap" "off")
   (command "circle" ratas1 "5")
   (command "circle" ratas2 "5")
   (command "arc" ratas1arc2 "e" ratas1arc1 "r" "7")
   (command "arc" ratas2arc2 "e" ratas2arc1 "r" "7")
   (command "line" ratas1arc1 riemasg1 riemasg2 riemasg3 "")
   (command "line" ratas2arc2 riemasp1 riemasp2 riemasp3 "")
   (command "arc" riemasg3 stogas riemasp3)
   (command "line" ratas1arc2 ratas2arc1 "")
)
